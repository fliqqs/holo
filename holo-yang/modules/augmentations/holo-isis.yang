module holo-isis {
  yang-version 1.1;
  namespace "http://holo-routing.org/yang/holo-isis";
  prefix holo-isis;

  import ietf-yang-types {
    prefix yang;
  }

  import ietf-inet-types {
    prefix inet;
  }

  import ietf-routing-types {
    prefix rt-types;
  }

  import ietf-routing {
    prefix rt;
  }

  import ietf-isis {
    prefix isis;
  }

  import ietf-te-types {
    prefix te-types;
  }

  import ietf-isis-link-attr {
    prefix isis-link-attr;
  }

  organization
    "Holo Routing Stack";

  description
    "This module defines augment statements for the ietf-isis
     module.";

  /*
   * Identities.
   */

  identity mt-topology {
    description
      "Base identity for IS-IS Multi-Topology (MT) types.";
  }

  identity mt-topology-standard {
    base mt-topology;
    description
      "Standard topology (MT-ID 0)";
  }

  identity mt-topology-ipv6-unicast {
    base mt-topology;
    description
      "IPv6 unicast topology (MT-ID 2)";
  }

  identity flooding-algorithm {
    description
      "Base identity for algorithms used to compute the flooding topology.";
    reference
      "draft-prz-lsr-interop-flood-reduction-architecture:
       Flooding Reduction Algorithms Framework";
  }

  identity flooding-algorithm-zero-pruner {
    base flooding-algorithm;
    description
      "Zero-pruner algorithm that uses the full flooding topology without
       pruning.";
    reference
      "draft-prz-lsr-interop-flood-reduction-architecture:
       Flooding Reduction Algorithms Framework";
  }

  identity flooding-algorithm-modified-manet {
    base flooding-algorithm;
    description
      "Modified MANET flooding reduction algorithm.";
    reference
      "draft-ietf-lsr-distoptflood:
       IS-IS Distributed Flooding Reduction";
  }

  /*
   * Types.
   */

  typedef extended-sequence-number-mode {
    type enumeration {
      enum "send-only" {
        description
          "Enables sending of the Extended Sequence Number TLV on PDUs,
           but does not enforce verification on received PDUs.";
      }
      enum "send-and-verify" {
        description
          "Enables sending of the Extended Sequence Number TLV and
           enforces verification on incoming PDUs. PDUs without this TLV
           or with invalid values will be discarded.";
      }
    }
    description
      "Configures the mode of operation for the Extended Sequence Number TLV.";
  }

  /*
   * Groupings.
   */

  grouping bier-protocol-extensions {
    description
      "Defines protocol extensions.";
    leaf mt-id {
      type uint8;
      description
        "Multi-topology associated with bier sub-domain.";
    }
    container bier {
      leaf enable {
        type boolean;
        default false;
        description
          "Enables bier protocol extensions.";
      }
      leaf advertise {
        type boolean;
        default true;
        description
          "Enable to advertise the parameters associated with bier.";
      }
      leaf receive {
        type boolean;
        default true;
        description
          "Enable to receive the parameters associated with bier.";
      }
      description
        "BIER global config.";
    }
  }

  grouping extended-sequence-number-cfg {
    leaf mode {
      type extended-sequence-number-mode;
      description
        "The operational mode for the Extended Sequence Number TLV on this
         interface.";
    }
  }

  /*
   * Augmentations.
   */

  augment "/rt:routing/rt:control-plane-protocols/"
        + "rt:control-plane-protocol/isis:isis" {
    description
      "IS-IS instance augmentations";
    container attached-bit {
      description "Configuration related to the ATT bit.";

      leaf suppress-advertisement {
        type boolean;
        default false;
        description
          "When enabled, prevents the setting of the ATT bit in level 1
           LSPs originated by this level 1/2 router. This ensures that
           level 1 routers in the area do not install a default route
           pointing to this router.";
      }

      leaf ignore-reception {
        type boolean;
        default false;
        description
          "When enabled, this level 1 router ignores the ATT bit in level
           1 LSPs it receives. As a result, it will not install a default
           route for any level 1/2 router that sets the ATT bit.";
      }
    }

    container inter-level-propagation-policies {
      description
        "Configuration options to control the propagation of routing information
         between IS-IS levels.";
      container level1-to-level2 {
        description
          "Configuration options to control the propagation of routing
           information from level 1 to level 2.";
        list summary-prefixes {
          description
            "List of summarization prefixes";
          key "prefix";
          leaf prefix {
            type inet:ip-prefix;
            description
              "The IP prefix to be advertised as a summary route into level 2.";
          }
          leaf metric {
            type uint32;
            description
              "Optional metric value for the summary route. If not specified,
               the lowest metric among the contributing more-specific level 1
               routes is used.";
          }
        }
      }
    }

    container flooding-reduction {
      description
        "Configuration for IS-IS flooding reduction extensions";
      leaf algorithm {
        type identityref {
          base flooding-algorithm;
        }
        default holo-isis:flooding-algorithm-zero-pruner;
        description
          "Specifies the flooding reduction algorithm in use.";
      }
    }

    container trace-options {
      description "Instance level trace options for IS-IS.";

      list flag {
        key name;
        description "List of tracing options.";
        leaf name {
          description
            "List of tracing options";
          type enumeration {
            enum flood-reduction;
            enum internal-bus;
            enum lsdb;
            enum packets-all;
            enum packets-hello;
            enum packets-psnp;
            enum packets-csnp;
            enum packets-lsp;
            enum spb;
            enum spf;
          }
        }
        leaf send {
          description "Trace sent packets.";
          type boolean;
          default true;
        }
        leaf receive {
          description "Trace received packets.";
          type boolean;
          default true;
        }
      }
    }
  }

  augment "/rt:routing/rt:control-plane-protocols/"
        + "rt:control-plane-protocol/isis:isis/"
        + "isis:address-families/isis:address-family-list" {
    list redistribution {
      key "level type";
      description
        "Parameters relating to route redistribution for the address family";

      leaf level {
        type isis:level-number;
        description
          "IS-IS level into which the routes are redistributed.";
      }
      leaf type {
        type identityref {
          base rt:control-plane-protocol;
        }
        description
          "Type of the control-plane protocol -- an identity
           derived from the 'control-plane-protocol'
           base identity.";
      }
    }
  }

  augment "/rt:routing/rt:control-plane-protocols/"
        + "rt:control-plane-protocol/isis:isis/"
        + "isis:authentication/"
        + "isis:authentication-type/isis:password" {
     leaf key-id {
      type uint16;
      description
        "Key identifier.";
    }
  }

  augment "/rt:routing/rt:control-plane-protocols/"
        + "rt:control-plane-protocol/isis:isis/"
        + "isis:authentication/isis:level-1/"
        + "isis:authentication-type/isis:password" {
     leaf key-id {
      type uint16;
      description
        "Key identifier.";
    }
  }

  augment "/rt:routing/rt:control-plane-protocols/"
        + "rt:control-plane-protocol/isis:isis/"
        + "isis:authentication/isis:level-2/"
        + "isis:authentication-type/isis:password" {
     leaf key-id {
      type uint16;
      description
        "Key identifier.";
    }
  }


  augment "/rt:routing/rt:control-plane-protocols/"
        + "rt:control-plane-protocol/isis:isis/"
        + "isis:interfaces/isis:interface" {
    description
      "IS-IS interface augmentations";

    container spb {
      description
        "Shortest Path Bridging parameters for this interface.";
      reference
        "RFC 6329: IS-IS Extensions Supporting IEEE 802.1aq
         Shortest Path Bridging";
      leaf enable {
        type boolean;
        default "false";
        description
          "Enables SPB on this interface. When enabled, an SPB-Metric
           Sub-TLV is advertised for the adjacency, which is what makes
           the adjacency eligible to carry SPB traffic.";
        reference
          "RFC 6329, Section 15.1: SPB Link Metric (SPB-Metric) Sub-TLV";
      }
      leaf link-metric {
        type uint32 {
          range "0..16777215";
        }
        default "10";
        description
          "24-bit SPB link metric advertised for this interface. SPB path
           computation uses the maximum of the two ends' advertised
           metrics, so a mismatch resolves to the larger value rather
           than producing asymmetric paths.";
        reference
          "RFC 6329, Section 11: Shortest Path Default Tie-Breaking";
      }
      leaf-list port-identifier {
        type uint16;
        description
          "Port identifiers advertised in the SPB-Metric Sub-TLV for
           this interface.";
      }
      leaf role {
        type enumeration {
          enum backbone {
            description
              "Backbone-facing (NNI): carries encapsulated frames between
               bridges.";
          }
          enum customer {
            description
              "Customer-facing (UNI): frames are encapsulated on ingress
               and decapsulated on egress.";
          }
        }
        default "backbone";
        description
          "Whether this interface faces the backbone or a customer. It
           determines which forwarding behaviour the data plane applies to
           the port.";
      }
      list uni-service {
        when "../role = 'customer'";
        key "i-sid";
        description
          "Services carried on this customer-facing interface.";
        leaf i-sid {
          type uint32 {
            range "0..16777215";
          }
          description
            "Service instance this interface belongs to.";
        }
      }
    }

    leaf csnp-disable {
      when "../isis:interface-type = 'point-to-point'";
      type boolean;
      default "false";
      description
        "If set to true, periodic CSNP PDUs are not transmitted on this
         interface. A single CSNP is still transmitted when the IS-IS
         adjacency is brought to the 'up' state.

         This leaf is only applicable to point-to-point interfaces.";
    }

    container trace-options {
      description "Interface level trace options for IS-IS.";

      list flag {
        key name;
        description "List of tracing options.";
        leaf name {
          description
            "List of tracing options";
          type enumeration {
            enum packets-all;
            enum packets-hello;
            enum packets-psnp;
            enum packets-csnp;
            enum packets-lsp;
          }
        }
        leaf send {
          description "Trace sent packets.";
          type boolean;
          default true;
        }
        leaf receive {
          description "Trace received packets.";
          type boolean;
          default true;
        }
      }
    }

    leaf state {
      config false;
      type enumeration {
        enum down {
          description
            "Interface is in the 'Down' state.";
        }
        enum up {
          description
            "Interface is in the 'Up' state.";
        }
      }
      description
        "Interface state.";
    }
    leaf circuit-id {
      config false;
      type isis:circuit-id;
      description
        "Interface circuit ID.";
    }
    leaf extended-circuit-id {
      config false;
      type isis:extended-circuit-id;
      description
        "Extended circuit ID of the interface.";
    }
  }

  augment "/rt:routing/rt:control-plane-protocols/"
        + "rt:control-plane-protocol/isis:isis/"
        + "isis:interfaces/isis:interface/"
        + "isis:hello-authentication/"
        + "isis:authentication-type/isis:password" {
     leaf key-id {
      type uint16;
      description
        "Key identifier.";
    }
  }

  augment "/rt:routing/rt:control-plane-protocols/"
        + "rt:control-plane-protocol/isis:isis/"
        + "isis:interfaces/isis:interface/"
        + "isis:hello-authentication/isis:level-1/"
        + "isis:authentication-type/isis:password" {
     leaf key-id {
      type uint16;
      description
        "Key identifier.";
    }
  }

  augment "/rt:routing/rt:control-plane-protocols/"
        + "rt:control-plane-protocol/isis:isis/"
        + "isis:interfaces/isis:interface/"
        + "isis:hello-authentication/isis:level-2/"
        + "isis:authentication-type/isis:password" {
     leaf key-id {
      type uint16;
      description
        "Key identifier.";
    }
  }

  augment "/rt:routing/rt:control-plane-protocols/"
        + "rt:control-plane-protocol/isis:isis/"
        + "isis:interfaces/isis:interface" {
      container extended-sequence-number {
        description
          "Controls the advertisement and processing of the Extended Sequence
           Number (ESN) TLV.";
        uses extended-sequence-number-cfg;
        container level-1 {
          uses extended-sequence-number-cfg;
          description
            "Configuration specific to level 1.";
        }
        container level-2 {
          uses extended-sequence-number-cfg;
          description
            "Configuration specific to level 2.";
        }
      }
    reference
      "RFC 7602: IS-IS Extended Sequence Number TLV";
  }

  augment "/rt:routing/rt:control-plane-protocols/"
        + "rt:control-plane-protocol/isis:isis/"
        + "isis:interfaces/isis:interface/"
        + "isis:topologies/isis:topology" {
    leaf enabled {
      type boolean;
      default "true";
      description
        "Enables or disables the topology.";
    }
  }

  augment "/rt:routing/rt:control-plane-protocols/"
        + "rt:control-plane-protocol/isis:isis/"
        + "isis:interfaces/isis:interface/"
        + "isis:adjacencies/isis:adjacency" {
    description
      "IS-IS interface adjacencies augmentations";
    leaf-list area-addresses {
      type isis:area-address;
      description
        "List of area addresses of the IS-IS node.  The IS-IS
         reference is TLV 1.";
    }
    leaf-list ipv4-addresses {
      type inet:ipv4-address;
      description
        "List of IPv4 addresses of the IS-IS node.  The IS-IS
         reference is TLV 132.";
    }
    leaf-list ipv6-addresses {
      type inet:ipv6-address;
      description
        "List of IPv6 addresses of the IS-IS node.  The IS-IS
         reference is TLV 232.";
    }
    leaf-list protocol-supported {
      type uint8;
      description
        "List of supported protocols of the IS-IS node.
         The IS-IS reference is TLV 129.";
    }
    container spb {
      description
        "SPB parameters received from this neighbour.";
      reference
        "RFC 6329, Section 13: SPB Sub-TLVs carried in IIH PDUs";
      leaf capable {
        type boolean;
        description
          "Whether the neighbour advertises NLPID 0xC1, indicating SPB
           support.";
      }
      leaf bidirectional {
        type boolean;
        description
          "Whether SPB is enabled locally and the neighbour advertises SPB
           support, so the adjacency can carry SPB traffic.";
      }
      leaf agreement {
        type enumeration {
          enum agreed;
          enum no-digest;
          enum not-valid;
          enum digest-mismatch;
          enum outstanding;
        }
        description
          "Whether this neighbour agrees with our view of the topology.
           Multicast forwarding for a tree whose shape changed is held back
           until every adjacency is in agreement.";
        reference
          "RFC 6329, Section 13.2: SPB-Digest Sub-TLV";
      }
      leaf agreement-number {
        type uint8 {
          range "0..3";
        }
        description
          "Agreement Number the neighbour is advertising.";
      }
      leaf discarded-agreement-number {
        type uint8 {
          range "0..3";
        }
        description
          "Agreement Number the neighbour has most recently discarded. Our
           own number is not acknowledged until this catches up with it.";
      }
      leaf region-match {
        type boolean;
        description
          "Whether the neighbour's SPB-MCID identifies the same SPT Region
           as ours. False means the two bridges are configured for
           different regions, which is a misconfiguration rather than a
           transient disagreement.";
        reference
          "RFC 6329, Section 13.1: SPB-MCID Sub-TLV";
      }
      list ect-vid {
        key "base-vid";
        description
          "ECT algorithm and Base VID pairs the neighbour advertises in
           its SPB-B-VID Sub-TLV. Under stable conditions these match the
           local ones; a difference indicates misconfiguration.";
        reference
          "RFC 6329, Section 13.3: SPB Base VLAN Identifiers Sub-TLV";
        leaf base-vid {
          type uint16 {
            range "0..4095";
          }
          description
            "Base VID advertised by the neighbour.";
        }
        leaf ect-algorithm {
          type uint32;
          description
            "ECT-ALGORITHM paired with that Base VID.";
        }
        leaf use {
          type boolean;
          description
            "U bit: the pair is in use by the neighbour or by some bridge
             in its LSDB.";
        }
        leaf multicast {
          type boolean;
          description
            "M bit: the Base VID carries multicast.";
        }
      }
    }
    leaf-list topologies {
      type uint16 {
        range "0 .. 4095";
      }
      description
        "List of topologies supported. The IS-IS reference is TLV 229.";
    }
  }

  augment "/rt:routing/rt:control-plane-protocols/"
        + "rt:control-plane-protocol/isis:isis/isis:database/"
        + "isis:levels" {
    leaf lsp-count {
      type yang:gauge32;
      description
        "The number of LSPs at this level with non-zero remaining lifetime.";
    }

    container fingerprint {
      description
        "Information about the LSDB fingerprint for this level.";

      leaf value {
        type uint64;
        description
          "A 64-bit fingerprint derived from the set of LSPs at this level.

           The fingerprint is computed by XOR-combining a per-LSP value
           for each LSP whose remaining lifetime is non-zero.

           The fingerprint is intended for detecting potential LSDB
           synchronization differences. Different values indicate
           different LSDB contents; identical values do not guarantee
           equivalence due to possible collisions.";
      }

      leaf last-update {
        type uint32;
        units "seconds";
        description
          "Time elapsed since the fingerprint for this level's LSDB was
           last updated.";
      }
    }
  }

  augment "/rt:routing/rt:control-plane-protocols/"
        + "rt:control-plane-protocol/isis:isis/isis:database/"
        + "isis:levels/isis:lsp" {
    leaf-list area-addresses {
      type isis:area-address;
      description
        "List of area addresses of the IS-IS node.  The IS-IS
         reference is TLV 1.";
    }
    leaf lsp-buffer-size {
      type uint16;
      units "bytes";
      description
        "The maximum sized LSP which may be generated.
         The IS-IS reference is TLV 14.";
    }
    leaf received-remaining-lifetime {
      type uint16;
      units "seconds";
      description
        "Remaining lifetime of this LSP at the time it was received.";
    }
    container purge-originator-identification {
      leaf originator {
        type isis:system-id;
        description
          "System ID of the router that generated the purged LSP.";
      }
      leaf received-from {
        type isis:system-id;
        description
          "System ID of the neighboring router from which the purged LSP
           was received.";
      }
    }
  }

  augment "/rt:routing/rt:control-plane-protocols/"
        + "rt:control-plane-protocol/isis:isis/isis:database/"
        + "isis:levels/isis:lsp/"
        + "isis:router-capabilities/isis:router-capability" {
    leaf flooding-algorithm {
      type uint8;
      description
        "Flooding reduction algorithm in use by the IS-IS node.";
    }
  }

  augment "/rt:routing/rt:control-plane-protocols/"
        + "rt:control-plane-protocol/isis:isis/isis:spf-control/"
        + "isis:ietf-spf-delay" {
    list level {
      config false;
      key "level";
      leaf level {
        type isis:level-number;
        description
          "IS-IS level.";
      }
      leaf current-state {
        type enumeration {
          enum quiet {
            description
              "QUIET state.";
          }
          enum short-wait {
            description
              "SHORT_WAIT state.";
          }
          enum long-wait {
            description
              "LONG_WAIT state.";
          }
        }
        config false;
        description
          "Current SPF Back-Off algorithm state.";
      }
      leaf remaining-time-to-learn {
        type rt-types:timer-value-milliseconds;
        units "msec";
        config false;
        description
          "Remaining time until the time-to-learn timer fires.";
      }
      leaf remaining-hold-down {
        type rt-types:timer-value-milliseconds;
        units "msec";
        config false;
        description
          "Remaining time until the hold-down timer fires.";
      }
      leaf last-event-received {
        type yang:timestamp;
        config false;
        description
          "Time of the last IGP event received.";
      }
      leaf next-spf-time {
        type yang:timestamp;
        config false;
        description
          "Time when the next SPF has been scheduled.";
      }
      leaf last-spf-time {
        type yang:timestamp;
        config false;
        description
          "Time of the last SPF computation.";
      }
    }
  }

  augment "/rt:routing/rt:control-plane-protocols/"
         + "rt:control-plane-protocol/isis:isis" {
     description
       "This augments IS-IS protocol configuration with bier.";
       container bier {
         uses bier-protocol-extensions;
         description
           "Control of bier advertisement and reception.";
       }
    }

  augment "/rt:routing/rt:control-plane-protocols/"
        + "rt:control-plane-protocol/isis:isis" {
    description
      "This augments IS-IS protocol configuration with SPB
       (Shortest Path Bridging) extensions.";
    container spb {
      description
        "Shortest Path Bridging (SPB) configuration for IS-IS.";
      reference
        "RFC 6329: IS-IS Extensions Supporting IEEE 802.1aq
         Shortest Path Bridging";
      leaf enable {
        type boolean;
        default "false";
        description
          "Enables SPB extensions for IS-IS. When enabled, the router
           will advertise NLPID 0xC1 (SPB) in the Protocols Supported
           TLV (TLV 129) of IIH (Hello) PDUs.";
        reference
          "RFC 6329, Section 13: Shortest Path Bridging NLPID";
      }
      leaf bridge-priority {
        type uint16;
        default "32768";
        description
          "Bridge Priority, forming the high-order two bytes of the
           BridgeID whose low-order six bytes are the IS-IS System ID.
           Because the BridgeID is the basis of ECT tie-breaking, this
           leaf gives the operator direct control over which equal-cost
           path is selected.";
        reference
          "RFC 6329, Section 11: Shortest Path Default Tie-Breaking";
      }
      container spsource-id {
        description
          "SPSourceID allocation. The SPSourceID occupies the upper 20
           bits of the multicast destination addresses of frames
           originated by this node.";
        reference
          "RFC 6329, Section 14.1: SPB Instance (SPB-Inst) Sub-TLV";
        leaf auto {
          type boolean;
          default "true";
          description
            "Allocate the SPSourceID automatically rather than using a
             configured value. This is advertised as the V bit of the
             SPB-Inst Sub-TLV.";
        }
        leaf value {
          when "../auto = 'false'";
          type uint32 {
            range "0..1048575";
          }
          description
            "Explicitly configured 20-bit SPSourceID. It must be unique
             within the SPB region; on collision the bridge with the
             highest priority Bridge Identifier keeps the value and the
             others must reallocate.";
        }
      }
      container region {
        description
          "Identity of the SPT Region, advertised in the SPB-MCID Sub-TLV.
           It must be configured identically on every bridge in the region;
           a mismatch means two bridges believe they are in different
           regions and is reported per adjacency.";
        reference
          "RFC 6329, Section 13.1: SPB-MCID Sub-TLV";
        leaf name {
          type string {
            length "0..32";
          }
          description
            "Configuration name of the region.";
        }
        leaf revision {
          type uint16;
          default "0";
          description
            "Revision level of the region's configuration.";
        }
        leaf config-digest {
          type yang:hex-string {
            length "47";
          }
          description
            "16-byte configuration digest of the region's VID allocation.
             Its computation is defined by IEEE 802.1Q; it is configured
             rather than derived here.";
        }
      }
      container dataplane {
        description
          "Connection to an external SPB dataplane, which is programmed with
           the computed forwarding tables.";
        leaf enable {
          type boolean;
          default "false";
          description
            "Enables programming of an external dataplane. With this
             disabled, SPB is computed and exposed as state but nothing is
             forwarded.";
        }
        leaf socket-path {
          type string;
          default "/var/run/spb-dp.sock";
          description
            "Unix socket of the dataplane agent.";
        }
      }
      list tree {
        key "base-vid";
        description
          "Tree sets operated by this SPB instance, each identified by a
           Base VID and built by an ECT algorithm. Advertised as the
           VLAN-ID tuples of the SPB-Inst Sub-TLV.";
        reference
          "RFC 6329, Section 14.1: SPB Instance (SPB-Inst) Sub-TLV";
        leaf base-vid {
          type uint16 {
            range "0..4095";
          }
          description
            "Base VID associated with this SPT Set.";
        }
        leaf algorithm {
          type uint8 {
            range "1..16";
          }
          default "1";
          description
            "Index of the standard IEEE 802.1 ECT-ALGORITHM used to build
             this tree set, selecting one of 00-80-C2-01 through
             00-80-C2-10. Index 1 is the default algorithm, which picks
             the path through the intermediate node with the lowest
             BridgeID.";
          reference
            "RFC 6329, Section 12: Shortest Path ECT";
        }
        leaf multicast {
          type boolean;
          default "true";
          description
            "Whether this Base VID carries multicast, advertised as the M
             bit of the VLAN-ID tuple.";
        }
        leaf spvid {
          type uint16 {
            range "0..4095";
          }
          description
            "Shortest Path VID, used in SPBV mode only. Its presence is
             advertised as the A bit of the VLAN-ID tuple.";
        }
      }
      list service {
        key "bmac base-vid";
        description
          "List of SPBM services to advertise via SPBM-SI Sub-TLV.
           Each entry represents a B-MAC address with associated
           service identifiers (I-SIDs).";
        reference
          "RFC 6329, Section 16.1: SPBM Service Identifier and
           Unicast Address Sub-TLV";
        leaf bmac {
          type yang:mac-address;
          description
            "B-MAC (Backbone MAC) address. This is the unicast MAC
             address used for SPBM forwarding. It can be the nodal
             B-MAC or a per-service B-MAC.";
        }
        leaf base-vid {
          type uint16 {
            range "0..4095";
          }
          description
            "Base VID (12 bits) that links this B-MAC to the
             corresponding ECT-ALGORITHM and SPT Set defined in
             the SPB-Inst Sub-TLV.";
        }
        list isid {
          key "value";
          description
            "List of I-SID (Service Identifier) entries associated
             with this B-MAC and Base VID combination.";
          leaf value {
            type uint32 {
              range "0..16777215";
            }
            description
              "24-bit I-SID (Service Identifier) value. This identifies
               a specific service instance in the SPBM network.";
          }
          leaf transmit {
            type boolean;
            default "true";
            description
              "T bit: When true, indicates transmit membership for
               this I-SID. The node will transmit frames for this
               service.";
          }
          leaf receive {
            type boolean;
            default "true";
            description
              "R bit: When true, indicates receive membership for
               this I-SID. The node will receive frames for this
               service.";
          }
        }
      }
    }
  }

  augment "/rt:routing/rt:control-plane-protocols/"
        + "rt:control-plane-protocol/isis:isis/holo-isis:spb" {
    description
      "Augments SPB configuration with the results of SPB computation.";
    container computed {
      config false;
      description
        "Shortest path trees and forwarding state derived from the SPB
         topology. This is what an external data plane is programmed with,
         and what offline tooling reads to reconstruct the topology.";
      leaf trees {
        type uint32;
        description
          "Number of shortest path trees currently computed.";
      }
      leaf trees-skipped {
        type uint32;
        description
          "Number of trees that were not computed because the internal
           tree limit was reached. A non-zero value means forwarding is
           incomplete.";
      }
      leaf generation {
        type uint64;
        description
          "Monotonic generation of the forwarding state, incremented
           whenever it changes. Used to reconcile with a data plane after
           either side restarts.";
      }
      leaf digest {
        type yang:hex-string;
        description
          "Our agreement digest: a summary of the topology that neighbours
           must match before multicast forwarding is updated.

           Its computation is defined by IEEE 802.1aq, which was not
           available; this is Holo's own and interoperates only with other
           Holo nodes.";
        reference
          "RFC 6329, Section 13.2";
      }
      leaf agreement-number {
        type uint8 {
          range "0..3";
        }
        description
          "Our Agreement Number, advanced whenever the digest changes.";
      }
      leaf agreed {
        type boolean;
        description
          "Whether every SPB adjacency currently agrees with us.";
      }
      leaf trees-withheld {
        type uint32;
        description
          "Trees whose multicast forwarding is being held back because
           their distance to the root changed and agreement has not yet
           been reached.";
      }
      leaf last-computation-duration {
        type uint32;
        units "microseconds";
        description
          "Duration of the most recent SPB computation.";
      }
      list spsource-id-conflict {
        key "spsource-id";
        description
          "SPSourceID values advertised by more than one node. The listed
           nodes lost the conflict and must reallocate; the node with the
           highest priority Bridge Identifier keeps the value.";
        reference
          "RFC 6329, Section 14.1: SPB Instance (SPB-Inst) Sub-TLV";
        leaf spsource-id {
          type uint32 {
            range "0..1048575";
          }
          description
            "The contended SPSourceID.";
        }
        leaf-list loser {
          type isis:system-id;
          description
            "Nodes that must reallocate their SPSourceID.";
        }
      }
      list tree {
        key "base-vid root";
        description
          "One shortest path tree, identified by its Base VID and root.
           The tree rooted at the local node drives unicast forwarding;
           trees rooted at remote multicast sources determine which
           branches the local node replicates onto.";
        leaf base-vid {
          type uint16 {
            range "0..4095";
          }
          description
            "Base VID of the tree set.";
        }
        leaf root {
          type isis:system-id;
          description
            "Node this tree is rooted at.";
        }
        leaf algorithm {
          type uint32;
          description
            "ECT-ALGORITHM used to build this tree.";
        }
        list node {
          key "system-id";
          description
            "Nodes reachable on this tree.";
          leaf system-id {
            type isis:system-id;
            description
              "The reachable node.";
          }
          leaf cost {
            type uint32;
            description
              "Accumulated SPB cost from the root, using the maximum of
               each link's two advertised metrics.";
          }
          leaf hops {
            type uint16;
            description
              "Hop count from the root.";
          }
          leaf parent {
            type isis:system-id;
            description
              "The node one hop closer to the root. There is exactly one,
               since SPB selects a single path rather than an ECMP set.";
          }
          leaf first-hop {
            type isis:system-id;
            description
              "The root's neighbour on the path to this node.";
          }
          leaf path-id {
            type string;
            description
              "The tie-breaking identity of the selected path: the sorted
               set of ECT-masked BridgeIDs of the nodes it traverses.
               Two paths are compared by cost, then hop count, then this
               value.";
            reference
              "RFC 6329, Sections 11 and 12";
          }
        }
      }
      list unicast {
        key "base-vid bmac";
        description
          "Unicast forwarding entries. The same table answers the
           mandatory ingress check: a frame arriving with a given
           {B-SA, B-VID} must have come from the node named here.";
        reference
          "RFC 6329, Section 4.2";
        leaf base-vid {
          type uint16 {
            range "0..4095";
          }
          description
            "Base VID of the entry.";
        }
        leaf bmac {
          type yang:mac-address;
          description
            "Destination B-MAC.";
        }
        leaf owner {
          type isis:system-id;
          description
            "Node that advertised this B-MAC.";
        }
        leaf nexthop {
          type isis:system-id;
          description
            "Adjacent node to forward through. Absent when the B-MAC is
             local.";
        }
        leaf cost {
          type uint32;
          description
            "SPB cost to the owning node.";
        }
      }
      list multicast {
        key "base-vid group-bmac";
        description
          "Multicast forwarding entries, one per (S, G) tree the local
           node participates in.";
        reference
          "RFC 6329, Section 4.4";
        leaf base-vid {
          type uint16 {
            range "0..4095";
          }
          description
            "Base VID of the entry.";
        }
        leaf group-bmac {
          type yang:mac-address;
          description
            "Group B-MAC, formed from the source's SPSourceID and the
             I-SID.";
        }
        leaf source {
          type isis:system-id;
          description
            "Node that roots this distribution tree.";
        }
        leaf i-sid {
          type uint32 {
            range "0..16777215";
          }
          description
            "Service instance carried by this tree.";
        }
        leaf local-deliver {
          type boolean;
          description
            "Whether the local node decapsulates and delivers to its own
             customer ports for this tree.";
        }
        leaf-list branch {
          type isis:system-id;
          description
            "Downstream branches the local node replicates onto: its
             children on the tree rooted at the source.";
        }
      }
      list service {
        key "i-sid";
        description
          "Service instances known in the region, with the local
           transmit/receive membership and the remote members.";
        leaf i-sid {
          type uint32 {
            range "0..16777215";
          }
          description
            "24-bit service instance identifier.";
        }
        leaf base-vid {
          type uint16 {
            range "0..4095";
          }
          description
            "Base VID carrying this service.";
        }
        leaf transmit {
          type boolean;
          description
            "Whether the local node transmits into this service.";
        }
        leaf receive {
          type boolean;
          description
            "Whether the local node receives from this service.";
        }
        list member {
          key "system-id";
          description
            "Remote nodes participating in this service.";
          leaf system-id {
            type isis:system-id;
            description
              "The participating node.";
          }
          leaf bmac {
            type yang:mac-address;
            description
              "B-MAC through which that node is reached for this
               service.";
          }
        }
      }
    }
  }

  augment "/rt:routing/rt:control-plane-protocols/"
        + "rt:control-plane-protocol/isis:isis/"
        + "isis:database/isis:levels/isis:lsp/"
        + "isis:extended-is-neighbor/isis:neighbor/"
        + "isis:instances/isis:instance" {
    description
      "Augments Extended IS neighbor instances with Extended
       Administrative Group sub-TLV data (RFC 7308).";
    leaf extended-admin-group {
      type te-types:extended-admin-group;
      description
        "Extended Administrative Group.";
      reference
        "RFC 7308: Extended Administrative Groups in MPLS
                   Traffic Engineering";
    }
  }

  augment "/rt:routing/rt:control-plane-protocols/"
        + "rt:control-plane-protocol/isis:isis/"
        + "isis:database/isis:levels/isis:lsp/"
        + "isis:mt-is-neighbor/isis:neighbor/"
        + "isis:instances/isis:instance" {
    description
      "Augments MT IS neighbor instances with Extended
       Administrative Group sub-TLV data (RFC 7308).";
    leaf extended-admin-group {
      type te-types:extended-admin-group;
      description
        "Extended Administrative Group.";
      reference
        "RFC 7308: Extended Administrative Groups in MPLS
                   Traffic Engineering";
    }
  }

  augment "/rt:routing/rt:control-plane-protocols/"
        + "rt:control-plane-protocol/isis:isis/"
        + "isis:database/isis:levels/isis:lsp/"
        + "isis:extended-is-neighbor/isis:neighbor/"
        + "isis:instances/isis:instance/"
        + "isis-link-attr:asla-sub-tlvs/"
        + "isis-link-attr:asla-sub-tlv" {
    description
      "Augments ASLA sub-TLV within Extended IS neighbor with
       Extended Administrative Group sub-TLV data (RFC 7308).";
    leaf extended-admin-group {
      type te-types:extended-admin-group;
      description
        "Extended Administrative Group.";
      reference
        "RFC 7308: Extended Administrative Groups in MPLS
                   Traffic Engineering";
    }
  }

  augment "/rt:routing/rt:control-plane-protocols/"
        + "rt:control-plane-protocol/isis:isis/"
        + "isis:database/isis:levels/isis:lsp/"
        + "isis:mt-is-neighbor/isis:neighbor/"
        + "isis:instances/isis:instance/"
        + "isis-link-attr:asla-sub-tlvs/"
        + "isis-link-attr:asla-sub-tlv" {
    description
      "Augments ASLA sub-TLV within MT IS neighbor with
       Extended Administrative Group sub-TLV data (RFC 7308).";
    leaf extended-admin-group {
      type te-types:extended-admin-group;
      description
        "Extended Administrative Group.";
      reference
        "RFC 7308: Extended Administrative Groups in MPLS
                   Traffic Engineering";
    }
  }

  augment "/rt:routing/rt:control-plane-protocols/"
        + "rt:control-plane-protocol/isis:isis/isis:database/"
        + "isis:levels/isis:lsp" {
    description
      "Augments LSP state with MT-Capability TLV information for SPB.";
    list mt-capability {
      config false;
      description
        "MT-Capability TLV (type 144) entries from this LSP.
         Contains SPB service information.";
      reference
        "RFC 6329, Section 16: MT-Capability TLV";
      leaf mt-id {
        type uint16 {
          range "0..4095";
        }
        description
          "Multi-Topology ID.";
      }
      leaf overload {
        type boolean;
        description
          "O-bit: When set, indicates the originating node is in
           overload state for this topology.";
      }
      container spb-instance {
        presence "The SPB-Inst Sub-TLV is present in this TLV.";
        description
          "SPB-Inst Sub-TLV (type 1) entry, carrying the originating
           node's SPSourceID, Bridge Priority and tree sets.";
        reference
          "RFC 6329, Section 14.1: SPB Instance (SPB-Inst) Sub-TLV";
        leaf cist-root-id {
          type uint64;
          description
            "CIST Root Identifier of the originating node's SPT Region.";
        }
        leaf cist-external-root-path-cost {
          type uint32;
          description
            "CIST External Root Path Cost.";
        }
        leaf bridge-priority {
          type uint16;
          description
            "Bridge Priority, the high-order two bytes of the BridgeID
             used for ECT tie-breaking.";
        }
        leaf spsource-id-auto {
          type boolean;
          description
            "V bit: the advertised SPSourceID was auto-allocated rather
             than configured.";
        }
        leaf spsource-id {
          type uint32 {
            range "0..1048575";
          }
          description
            "20-bit SPSourceID used to construct the multicast
             destination addresses of frames originated by this node. The
             value zero means dynamic allocation has not yet completed.";
        }
        list vlan-id-tuple {
          description
            "Tree sets advertised by the originating node, each pairing
             an ECT-ALGORITHM with a Base VID.";
          leaf ect-algorithm {
            type uint32;
            description
              "ECT-ALGORITHM: an OUI in the top 24 bits and an algorithm
               index in the low 8 bits. The 16 standard IEEE 802.1
               algorithms are 00-80-C2-01 through 00-80-C2-10.";
            reference
              "RFC 6329, Section 12: Shortest Path ECT";
          }
          leaf base-vid {
            type uint16 {
              range "0..4095";
            }
            description
              "Base VID associated with this SPT Set.";
          }
          leaf spvid {
            type uint16 {
              range "0..4095";
            }
            description
              "Shortest Path VID, used in SPBV mode.";
          }
          leaf use {
            type boolean;
            description
              "U bit: this ECT-ALGORITHM and Base VID pair is in use.";
          }
          leaf multicast {
            type boolean;
            description
              "M bit: this Base VID carries multicast.";
          }
          leaf spvid-allocated {
            type boolean;
            description
              "A bit: an SPVID has been allocated for this tuple.";
          }
        }
      }
      list spbm-service {
        description
          "SPBM-SI Sub-TLV entries (type 3) containing service
           identifier and unicast address information.";
        reference
          "RFC 6329, Section 16.1: SPBM Service Identifier and
           Unicast Address Sub-TLV";
        leaf bmac {
          type yang:mac-address;
          description
            "B-MAC (Backbone MAC) address for SPBM forwarding.";
        }
        leaf base-vid {
          type uint16 {
            range "0..4095";
          }
          description
            "Base VID linking to ECT-ALGORITHM and SPT Set.";
        }
        list isid {
          description
            "I-SID (Service Identifier) entries.";
          leaf value {
            type uint32 {
              range "0..16777215";
            }
            description
              "24-bit I-SID value.";
          }
          leaf transmit {
            type boolean;
            description
              "T bit: Transmit membership for this I-SID.";
          }
          leaf receive {
            type boolean;
            description
              "R bit: Receive membership for this I-SID.";
          }
        }
      }
    }
  }
}
